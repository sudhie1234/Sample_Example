# temp

# Specification: Wiper_swreq

## WMREQ001: Inputs/Outputs to the System

### WMREQ001_1: Input_1 - Ignition

### WMREQ001_2: Input_2 - Rain_Sensor

### WMREQ001_3: Input_3 - Knob

### WMREQ001_4: Output - Wiper_Output

## WMREQ002: Logical Connections inside systems

### WMREQ002_1: Intermediate_1 = Rain_Sensor OR Knob

### WMREQ002_2: Wiper = Intermediate_1 AND Ignition

### WMREQ002_3: Compare to Constant (Equal to 1)

## WMREQ003: Wiper Enable behaviour
| Wiper Output is only enabled when Ignition Switch is ON |
| --- |

### WMREQ003_1: Wiper=ENABLE if Ignition=ON

## WMREQ004: Rain Sensor Activation
| The Wiper Output shall turn ON if the Rain Sensor senses water droplets, only if the Ignition Switch is ON |
| --- |

### WMREQ004_1: Wiper=ON if (Rain_Sensor=1 OR Knob=0) AND Ignition=1

## WMREQ005: Knob Activation
| The Wiper Output shall turn ON if the Knob is manually turned ON, only if the Ignition Switch is ON |
| --- |

### WMREQ005_1: Wiper=ON if (Rain_Sensor=0 OR Knob=1) AND Ignition=1

## WMREQ006: Rain Sensor and Knob Activation
| The Wiper Output shall turn ON if both the Rain Sensor senses water droplets AND Knob is Turned ON with Ignition Switch ON |
| --- |

### WMREQ006_1: Wiper=ON if (Rain_Sensor=1 OR Knob=1)AND Ignition=1

## WMREQ007: Wiper Disable Behavior1
| Regardless of the inputs of Ignition Switch is ON, the wiper should be OFF if both the inputs of Rain Sensor and Knob to the Wiper, are OFF |
| --- |

### WMREQ007_1: Wiper=ON if (Rain_Sensor=0 OR Knob=0)AND Ignition=1

## WMREQ008: Wiper Disable Behavior2
| Regardless of the inputs of Rain Sensor and Knob to the Wiper, it should be OFF if the Ignition Switch is OFF |
| --- |

### WMREQ008_1: Wiper=OFF if (Rain_Sensor=1 OR Knob=1)AND Ignition=0
