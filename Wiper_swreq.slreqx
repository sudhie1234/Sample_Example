# Wiper_swreq

## WMREQ003: Wiper Enable behaviour (Functional)
| Wiper Output is only enabled when Ignition Switch is ON |
| --- |

### WMREQ003_1: Wiper=ENABLE if Ignition=ON (Functional)

## WMREQ004: Rain Sensor Activation (Functional)
| The Wiper Output shall turn ON if the Rain Sensor senses water droplets, only if the Ignition Switch is ON |
| --- |

### WMREQ004_1: Wiper=ON if (Rain_Sensor=1 OR Knob=0) AND Ignition=1 (Functional)

## WMREQ005: Knob Activation (Functional)
| The Wiper Output shall turn ON if the Knob is manually turned ON, only if the Ignition Switch is ON |
| --- |

### WMREQ005_1: Wiper=ON if (Rain_Sensor=0 OR Knob=1) AND Ignition=1 (Functional)

## WMREQ006: Rain Sensor and Knob Activation (Functional)
| The Wiper Output shall turn ON if both the Rain Sensor senses water droplets AND Knob is Turned ON with Ignition Switch ON |
| --- |

### WMREQ006_1: Wiper=ON if (Rain_Sensor=1 OR Knob=1)AND Ignition=1 (Functional)

## WMREQ007: Wiper Disable Behavior1 (Functional)
| Regardless of the inputs of Ignition Switch is ON, the wiper should be OFF if both the inputs of Rain Sensor and Knob to the Wiper, are OFF |
| --- |

### WMREQ007_1: Wiper=ON if (Rain_Sensor=0 OR Knob=0)AND Ignition=1 (Functional)

## WMREQ008: Wiper Disable Behavior2 (Functional)
| Regardless of the inputs of Rain Sensor and Knob to the Wiper, it should be OFF if the Ignition Switch is OFF |
| --- |

### WMREQ008_1: Wiper=OFF if (Rain_Sensor=1 OR Knob=1)AND Ignition=0 (Functional)

## WMREQ001: Inputs/Outputs to the System (Informational)

### WMREQ001_3: Input_3 - Knob (Functional)

### WMREQ001_4: Output - Wiper_Output (Functional)

### WMREQ001_1: Input_1 - Ignition (Functional)

### WMREQ001_2: Input_2 - Rain_Sensor (Functional)

## WMREQ002: Logical Connections inside systems (Functional)

### WMREQ002_1: Intermediate_1 = Rain_Sensor OR Knob (Functional)

### WMREQ002_2: Wiper = Intermediate_1 AND Ignition (Functional)

### WMREQ002_3: Compare to Constant (Equal to 1) (Functional)
